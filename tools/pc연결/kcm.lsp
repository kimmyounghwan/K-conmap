;;; K-적산컨맵 연결 1.1 - 캐드 명령 KCM · KCMS (K-건설맵 · k-conmap.com)
;;; KCM  : 지금 도면을 저장하고 "K-적산컨맵 연결" 프로그램의 보내기 폴더에 도면 경로 한 줄을 씁니다.
;;;        프로그램이 그것을 보고 적산컨맵 작업 화면을 열어 이 도면을 넣습니다(도면은 이 PC 안에서만 오감).
;;; KCMS : 캐드에서 고른 것(선 · 폴리선 · 호 · 원 · 타원 · 블록 · 치수 · 글자)의 좌표 · 레이어 · 핸들을 보내기 폴더에 씁니다.
;;;        작업 화면 "캐드" 탭이 받아 길이 · 면적 · 개수를 셈하고, 높이 · 공제 · 횟수는 화면에서 넣습니다(도면 파일은 보내지 않음).
;;; 넣는 법: 캐드 명령 APPLOAD -> 이 파일(kcm.lsp) -> 불러오기. "시작하기 세트" 에 넣으면 캐드를 켤 때마다 들어옵니다.
;;; 오토캐드 · 오토캐드 LT(2024 이상) · ZWCAD · 캐디안에서 씁니다(순수 AutoLISP 만 씀 - vla · DCL 안 씀).
;;; KCMS 글 꼴(판 1)은 건설맵 web/src/lib/캐드고름.js 머리 설명과 같아야 합니다(시험 tools/시험_캐드고름리습.py).
(defun c:KCM ( / a d p fn f)
  (setq a (getenv "APPDATA"))
  (cond
    ((not a)
      (princ "\n[KCM] APPDATA 폴더를 찾지 못했습니다."))
    ((= 0 (getvar "DWGTITLED"))
      (princ "\n[KCM] 이름 없는 도면입니다 - 먼저 저장(SAVEAS)한 뒤 다시 KCM 을 치십시오."))
    (T
      (command "_.QSAVE")
      (setq d (strcat a "\\K-conmap\\연결\\보내기"))
      (setq p (strcat (getvar "DWGPREFIX") (getvar "DWGNAME")))
      (setq fn (strcat d "\\kcm_" (rtos (* 100000 (rem (getvar "DATE") 1)) 2 0) ".txt"))
      (setq f (open fn "w"))
      (if f
        (progn (write-line p f) (close f) (princ (strcat "\n[KCM] 적산컨맵으로 보냄: " p)))
        (princ "\n[KCM] 보내지 못했습니다 - K-적산컨맵 연결 프로그램을 먼저 켜 주십시오(건설맵 사이트에서 받음).")))
  )
  (princ)
)

;;; ---- KCMS 도움 함수(이름 앞 kcms- : 다른 리습과 안 겹치게) ----
(defun kcms-s (v)
  (cond ((null v) "") ((eq (type v) 'STR) v) ((eq (type v) 'INT) (itoa v)) ((eq (type v) 'REAL) (rtos v 2 8)) (T ""))
)
(defun kcms-n (x) (if (numberp x) (rtos x 2 8) "0"))
(defun kcms-g (k e) (cdr (assoc k e)))
(defun kcms-num (k e d / v) (setq v (cdr (assoc k e))) (if (numberp v) v d))
(defun kcms-int (k e d / v) (setq v (cdr (assoc k e))) (if (eq (type v) 'INT) v d))
(defun kcms-z (p) (if (and (listp p) (numberp (caddr p))) (caddr p) 0.0))
(defun kcms-pt (p)
  (if (and (listp p) (numberp (car p)) (numberp (cadr p))) (strcat (kcms-n (car p)) "," (kcms-n (cadr p))) "")
)
;; 탭 · 줄바꿈을 빈칸으로(한 객체 = 한 줄 · 칸 = 탭)
(defun kcms-clean (s / i n c out)
  (if (not (eq (type s) 'STR)) (setq s ""))
  (setq i 1 n (strlen s) out "")
  (while (<= i n)
    (setq c (substr s i 1))
    (if (member c (list (chr 9) (chr 10) (chr 13))) (setq c " "))
    (setq out (strcat out c) i (1+ i))
  )
  out
)
;; 돌출 방향(210) - (0 0 1) 이면 빈칸
(defun kcms-ext (e / n)
  (setq n (kcms-g 210 e))
  (if (and (listp n) (numberp (car n)) (numberp (cadr n)) (numberp (caddr n))
           (or (/= 0.0 (car n)) (/= 0.0 (cadr n)) (/= 1.0 (caddr n))))
    (strcat (kcms-n (car n)) "," (kcms-n (cadr n)) "," (kcms-n (caddr n)))
    ""
  )
)
;; 여러 줄 글(MTEXT) - (3 . 앞 토막) ... (1 . 끝 토막)
(defun kcms-text (e / s)
  (setq s "")
  (foreach x e (if (and (listp x) (= (car x) 3)) (setq s (strcat s (kcms-s (cdr x))))))
  (strcat s (kcms-s (kcms-g 1 e)))
)
;; 가벼운 폴리선 꼭짓점 - "x,y,볼록;..."
(defun kcms-lwpts (e / s p b)
  (setq s "" p nil b 0.0)
  (foreach x e
    (cond
      ((and (listp x) (= (car x) 10))
        (if p (setq s (strcat s (if (= s "") "" ";") (kcms-pt p) "," (kcms-n b))))
        (setq p (cdr x) b 0.0))
      ((and (listp x) (= (car x) 42) p (numberp (cdr x))) (setq b (cdr x)))
    )
  )
  (if p (setq s (strcat s (if (= s "") "" ";") (kcms-pt p) "," (kcms-n b))))
  s
)
;; 옛 폴리선(POLYLINE) 꼭짓점 - VERTEX 를 따라감(스플라인 틀 점 = 꼴 16 은 뺌) -> ("x,y,볼록;..." . ",z1,z2,...")
(defun kcms-plpts (en / s zs v e f)
  (setq s "" zs "" v (entnext en))
  (while (and v (setq e (entget v)) (= (kcms-g 0 e) "VERTEX"))
    (setq f (kcms-int 70 e 0))
    (if (= 0 (logand 16 f))
      (setq s (strcat s (if (= s "") "" ";") (kcms-pt (kcms-g 10 e)) "," (kcms-n (kcms-num 42 e 0.0)))
            zs (strcat zs "," (kcms-n (kcms-z (kcms-g 10 e))))))
    (setq v (entnext v))
  )
  (cons s zs)
)
;; 객체 하나 -> 한 줄 "종류 레이어 핸들 닫힘 z 점들 값들 글 돌출"(칸 = 탭)
(defun kcms-row (en / e ty cl z pts vals txt ext a b q tb)
  (setq tb (chr 9)
        e (entget en)
        ty (kcms-s (kcms-g 0 e))
        cl "0" z "0" pts "" vals "" txt ""
        ext (kcms-ext e))
  (cond
    ((= ty "LINE")
      (setq a (kcms-g 10 e) b (kcms-g 11 e)
            pts (strcat (kcms-pt a) ";" (kcms-pt b))
            z (kcms-n (kcms-z a))
            vals (strcat (kcms-n (kcms-z a)) "," (kcms-n (kcms-z b)))
            ext ""))
    ((= ty "LWPOLYLINE")
      (setq cl (if (= 1 (logand 1 (kcms-int 70 e 0))) "1" "0")
            z (kcms-n (kcms-num 38 e 0.0))
            pts (kcms-lwpts e)))
    ((= ty "POLYLINE")
      (setq a (kcms-int 70 e 0)
            cl (if (= 1 (logand 1 a)) "1" "0")
            z (kcms-n (kcms-z (kcms-g 10 e)))
            q (kcms-plpts en)
            pts (car q)
            vals (strcat (itoa a) (cdr q))))
    ((= ty "ARC")
      (setq a (kcms-g 10 e)
            z (kcms-n (kcms-z a))
            vals (strcat (kcms-pt a) "," (kcms-n (kcms-num 40 e 0.0)) "," (kcms-n (kcms-num 50 e 0.0)) "," (kcms-n (kcms-num 51 e 0.0)))))
    ((= ty "CIRCLE")
      (setq a (kcms-g 10 e)
            z (kcms-n (kcms-z a))
            vals (strcat (kcms-pt a) "," (kcms-n (kcms-num 40 e 0.0)))))
    ((= ty "ELLIPSE")
      (setq a (kcms-g 10 e) b (kcms-g 11 e)
            z (kcms-n (kcms-z a))
            vals (strcat (kcms-pt a) "," (kcms-pt b) "," (kcms-n (kcms-num 40 e 1.0)) "," (kcms-n (kcms-num 41 e 0.0)) "," (kcms-n (kcms-num 42 e 0.0)))))
    ((= ty "INSERT")
      (setq a (kcms-g 10 e)
            z (kcms-n (kcms-z a))
            pts (kcms-pt a)
            vals (strcat (kcms-n (kcms-num 41 e 1.0)) "," (kcms-n (kcms-num 42 e 1.0)) "," (kcms-n (kcms-num 50 e 0.0)) "," (itoa (kcms-int 70 e 0)) "," (itoa (kcms-int 71 e 0)))
            txt (kcms-clean (kcms-g 2 e))))
    ((or (= ty "TEXT") (= ty "MTEXT"))
      (setq a (kcms-g 10 e)
            pts (kcms-pt a)
            vals (kcms-n (kcms-num 40 e 0.0))
            txt (kcms-clean (kcms-text e))))
    ((= ty "DIMENSION")
      (setq a (kcms-g 13 e) b (kcms-g 14 e)
            pts (if (and a b) (strcat (kcms-pt a) ";" (kcms-pt b)) "")
            vals (strcat (kcms-n (kcms-num 42 e 0.0)) "," (itoa (kcms-int 70 e 0)) "," (kcms-n (kcms-num 50 e 0.0)))
            txt (kcms-clean (kcms-g 1 e))
            ext ""))
  )
  (strcat ty tb (kcms-clean (kcms-g 8 e)) tb (kcms-s (kcms-g 5 e)) tb cl tb z tb pts tb vals tb txt tb ext)
)

;;; ---- KCMS : 고른 것을 적산컨맵 작업 화면 "캐드" 탭으로 ----
(defun c:KCMS ( / *error* a d ss n i k nm fn tx f memo tb)
  (defun *error* (msg)
    (if f (close f))
    (setq f nil)
    (princ (strcat "\n[KCMS] 멈춤: " (kcms-s msg)))
    (princ)
  )
  (setq a (getenv "APPDATA") tb (chr 9))
  (cond
    ((not a)
      (princ "\n[KCMS] APPDATA 폴더를 찾지 못했습니다."))
    (T
      (setq d (strcat a "\\K-conmap\\연결\\보내기"))
      (princ "\n[KCMS] 적산컨맵으로 보낼 것을 고르십시오(선 · 폴리선 · 호 · 원 · 블록 · 치수 · 글자 - 다 고른 뒤 엔터).")
      (setq ss (ssget))
      (cond
        ((not ss)
          (princ "\n[KCMS] 고른 것이 없습니다."))
        ((> (sslength ss) 5000)
          (princ (strcat "\n[KCMS] 너무 많습니다(" (itoa (sslength ss)) "개) - 5,000개까지 나눠서 보내 주십시오.")))
        (T
          (setq memo (getstring T "\n[KCMS] 적요 - 무엇인지(예: 1층 벽 W1 · 엔터 = 건너뜀): "))
          (setq n (sslength ss)
                k (rem (fix (* 100000 (rem (getvar "DATE") 1))) 500)
                nm (strcat "kcms_" (itoa k))
                fn (strcat d "\\" nm ".csv")
                tx (strcat d "\\" nm ".txt")
                f (open fn "w"))
          (if (not f)
            (princ "\n[KCMS] 보내지 못했습니다 - K-적산컨맵 연결 프로그램을 먼저 켜 주십시오(건설맵 사이트에서 받음).")
            (progn
              (write-line (strcat "KCMSEL" tb "1" tb (kcms-s (getvar "DWGPREFIX")) (kcms-s (getvar "DWGNAME")) tb (kcms-s (getvar "INSUNITS")) tb (kcms-clean memo) tb (itoa n) tb (kcms-s (getvar "ACADVER")) tb (kcms-s (getvar "PRODUCT"))) f)
              (setq i 0)
              (while (< i n)
                (write-line (kcms-row (ssname ss i)) f)
                (setq i (1+ i))
              )
              (close f)
              (setq f (open tx "w"))
              (if f
                (progn
                  (write-line fn f)
                  (close f)
                  (setq f nil)
                  (princ (strcat "\n[KCMS] 적산컨맵으로 보냄: " (itoa n) "개 - 작업 화면 \"캐드\" 탭에서 봅니다.")))
                (princ "\n[KCMS] 보내지 못했습니다 - 보내기 폴더에 쓸 수 없습니다.")))))))
  )
  (setq f nil)
  (princ)
)
(princ "\nK-적산컨맵 연결 1.1 - 명령 KCM: 지금 도면을 적산컨맵으로 · KCMS: 고른 것을 적산컨맵 \"캐드\" 탭으로. (K-건설맵 · k-conmap.com)")
(princ)
